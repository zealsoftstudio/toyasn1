-- TOYASN1 PROTOCOL
--

TOYASN1-PROTOCOL DEFINITIONS ::=
BEGIN

TOYASN1-MESSAGE  ::= [APPLICATION 0] IMPLICIT SEQUENCE {
    name			    [1] OBJECT IDENTIFIER OPTIONAL,
    title			    [2] OBJECT IDENTIFIER OPTIONAL
}

END
